module a-module-deviations {
  yang-version 1.1;
  namespace "urn:example:deviations";
  prefix amd;

  import a-module {
    prefix a;
  }
  import str-type {
    prefix str;
  }


  include "c-module";

  deviation "/a:something/a:a-enum" {
    deviate replace {
      type c-enum;
    }
  }
  deviation "/a:something/a:str-value" {
    deviate replace {
      type str:int-string;
    }
  }
}
