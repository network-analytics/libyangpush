submodule c-module {
yang-version 1.1;
belongs-to a-module {
prefix a;
}
import e-module {
prefix e;
revision-date 2023-06-13;
}

include "cc-module";
grouping somegroup {
leaf c-leaf {
type e:e-enum;
}
uses cc-somegroup;
}
}
