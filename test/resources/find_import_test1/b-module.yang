module b-module {
  yang-version 1.1;
  namespace "urn:example:yang:b-module";
  prefix b;

  import e-module {
    prefix e;
    revision-date 2023-06-13;
  }


  include "c-module";

  revision 2023-06-13;

  typedef myenum {
    type e:e-enum;
  }

  typedef bar {
    type enumeration {
      enum "zero";
    }
    description
      "test";
  }
}
