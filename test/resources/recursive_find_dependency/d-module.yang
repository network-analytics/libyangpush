module d-module {
  yang-version 1.1;
  namespace "urn:example:yang:d-module";
  prefix d;

  import a-module {
    prefix a;
  }
  import b-module {
    prefix b;
  }

  augment "/a:a" {
    container y {
      leaf y-leaf {
        type b:myenum;
      }
    }
  }
}
