module b-module {
  yang-version 1.1;
  namespace "urn:example:yang:b-module";
  prefix b;

  import e-module {
    prefix e;
    revision-date 2023-06-13;
  }

  revision 2023-06-13;

  typedef myenum {
    type enumeration {
      enum "zero";
    }
  }

  typedef bar {
    type enumeration {
      enum "zero";
    }
    description
      "test";
  }

  grouping some-other-groups {
    uses e:some-groups;
  }
}
