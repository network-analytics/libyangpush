module d-module {
  yang-version 1.1;
  namespace "urn:example:yang:d-module";
  prefix d;

  import a-module {
    prefix a;
  }
  import e-module {
    prefix e;
    revision-date 2023-06-13;
  }


  augment "/a:a" {
    container y {
      leaf y-leaf {
        type e:e-enum;
      }
    }
  }
}
